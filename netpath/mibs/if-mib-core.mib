IF-MIB-CORE DEFINITIONS ::= BEGIN

-- Bundled with SappiWhere so the OIDs Nodes already polls every cycle
-- (see nodeoids.py's IF_TABLE/IFX_TABLE) show real DESCRIPTION text and
-- enum tables in the MIB browser, not just a bare name. This is a
-- hand-written subset covering only those columns, not a full copy of
-- RFC 2863's IF-MIB -- OID numbering and column meaning follow that
-- public IETF standard, restated here in this app's own words.

ifMIB          OBJECT IDENTIFIER ::= { mib-2 31 }
ifMIBObjects   OBJECT IDENTIFIER ::= { ifMIB 1 }
ifXTable       OBJECT IDENTIFIER ::= { ifMIBObjects 1 }
ifXEntry       OBJECT IDENTIFIER ::= { ifXTable 1 }

interfaces     OBJECT IDENTIFIER ::= { mib-2 2 }
ifTable        OBJECT IDENTIFIER ::= { interfaces 2 }
ifEntry        OBJECT IDENTIFIER ::= { ifTable 1 }

ifIndex OBJECT-TYPE
    SYNTAX      INTEGER
    MAX-ACCESS  read-only
    STATUS      current
    DESCRIPTION
        "A unique value identifying this interface, greater than zero,
        assigned by the agent and stable across reboots for as long as
        the interface remains configured."
    ::= { ifEntry 1 }

ifDescr OBJECT-TYPE
    SYNTAX      DisplayString
    MAX-ACCESS  read-only
    STATUS      current
    DESCRIPTION
        "A textual description of the interface, typically including
        its manufacturer, product name, and hardware/software version."
    ::= { ifEntry 2 }

ifType OBJECT-TYPE
    SYNTAX      INTEGER
    MAX-ACCESS  read-only
    STATUS      current
    DESCRIPTION
        "The interface's media type, from IANAifType-MIB's registry
        (e.g. ethernetCsmacd, ppp, softwareLoopback)."
    ::= { ifEntry 3 }

ifMtu OBJECT-TYPE
    SYNTAX      INTEGER
    MAX-ACCESS  read-only
    STATUS      current
    DESCRIPTION
        "The largest datagram this interface can send or receive, in
        octets, at the protocol layer immediately above it."
    ::= { ifEntry 4 }

ifSpeed OBJECT-TYPE
    SYNTAX      Gauge32
    MAX-ACCESS  read-only
    STATUS      current
    DESCRIPTION
        "The interface's current bandwidth in bits per second. A 32-bit
        counter, so a link at or above 4.29 Gbps reports the same
        4294967295 ceiling -- ifHighSpeed below carries the real figure
        for those links."
    ::= { ifEntry 5 }

ifPhysAddress OBJECT-TYPE
    SYNTAX      PhysAddress
    MAX-ACCESS  read-only
    STATUS      current
    DESCRIPTION
        "The interface's address at its protocol sub-layer, such as a
        MAC address for an 802.x interface; empty for an interface with
        no such address."
    ::= { ifEntry 6 }

ifAdminStatus OBJECT-TYPE
    SYNTAX      INTEGER { up(1), down(2), testing(3) }
    MAX-ACCESS  read-write
    STATUS      current
    DESCRIPTION
        "The interface's desired state, as configured by an operator --
        distinct from ifOperStatus, its actual current state."
    ::= { ifEntry 7 }

ifOperStatus OBJECT-TYPE
    SYNTAX      INTEGER { up(1), down(2), testing(3), unknown(4),
                          dormant(5), notPresent(6), lowerLayerDown(7) }
    MAX-ACCESS  read-only
    STATUS      current
    DESCRIPTION
        "The interface's actual current operational state."
    ::= { ifEntry 8 }

ifInOctets OBJECT-TYPE
    SYNTAX      Counter32
    MAX-ACCESS  read-only
    STATUS      current
    DESCRIPTION
        "Total octets received on this interface, including framing.
        Wraps at 2^32; ifHCInOctets below is the 64-bit column preferred
        on any link fast enough to wrap this one between polls."
    ::= { ifEntry 10 }

ifInErrors OBJECT-TYPE
    SYNTAX      Counter32
    MAX-ACCESS  read-only
    STATUS      current
    DESCRIPTION
        "Count of inbound packets discarded because they contained
        errors preventing delivery to a higher-layer protocol."
    ::= { ifEntry 14 }

ifOutOctets OBJECT-TYPE
    SYNTAX      Counter32
    MAX-ACCESS  read-only
    STATUS      current
    DESCRIPTION
        "Total octets transmitted from this interface, including
        framing. Wraps at 2^32; ifHCOutOctets below is the 64-bit
        column preferred on any link fast enough to wrap this one
        between polls."
    ::= { ifEntry 16 }

ifOutErrors OBJECT-TYPE
    SYNTAX      Counter32
    MAX-ACCESS  read-only
    STATUS      current
    DESCRIPTION
        "Count of outbound packets that could not be transmitted
        because of an error."
    ::= { ifEntry 20 }

ifName OBJECT-TYPE
    SYNTAX      DisplayString
    MAX-ACCESS  read-only
    STATUS      current
    DESCRIPTION
        "The interface's short operator-facing name, such as the name
        it would be referred to in command-line configuration."
    ::= { ifXEntry 1 }

ifHCInOctets OBJECT-TYPE
    SYNTAX      Counter64
    MAX-ACCESS  read-only
    STATUS      current
    DESCRIPTION
        "The 64-bit counterpart to ifInOctets, present on high-speed
        interfaces so a rate calculation between two polls does not
        misread a genuine multi-wrap of the 32-bit counter as a reset."
    ::= { ifXEntry 6 }

ifHCOutOctets OBJECT-TYPE
    SYNTAX      Counter64
    MAX-ACCESS  read-only
    STATUS      current
    DESCRIPTION
        "The 64-bit counterpart to ifOutOctets, present on high-speed
        interfaces so a rate calculation between two polls does not
        misread a genuine multi-wrap of the 32-bit counter as a reset."
    ::= { ifXEntry 10 }

ifHighSpeed OBJECT-TYPE
    SYNTAX      Gauge32
    MAX-ACCESS  read-only
    STATUS      current
    DESCRIPTION
        "The interface's current bandwidth in millions of bits per
        second -- the column to trust over ifSpeed once a link is fast
        enough for ifSpeed's 32-bit ceiling to be ambiguous."
    ::= { ifXEntry 15 }

ifAlias OBJECT-TYPE
    SYNTAX      DisplayString
    MAX-ACCESS  read-write
    STATUS      current
    DESCRIPTION
        "An operator-assigned label for this interface, such as a
        circuit ID or a plain-language description of what it connects
        to -- not generated by the device itself."
    ::= { ifXEntry 18 }

END
